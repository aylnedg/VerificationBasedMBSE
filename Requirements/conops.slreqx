# conops

## #36: Surveillance Capability (Functional)
The system shall provide surveillance capabilities to support search and rescue missions

### #37: Human Search and Rescue with UAV (Functional)
The system shall use UAV to locate people during search and rescue missions with use of payloads, full motion video.

## #38: Communications Capability (Functional)
The system shall provide communication capabilities to coordinate with launch platform to support search and rescue efforts during missions.

## #39: Imaging Capability (Functional)
The system shall perform various imaging capabilities for search and rescue

### #40: Image Capture (Functional)
The UAV shall include a payload sensor capable of capturing images in the visible light spectrum.

### #41: Image Processing (Functional)
The UAV shall have image-processing capabilities to support identifying locations of interest and distinguishing lost personnel for search and rescue mission.

### #42: Imagery Intelligence (Functional)
The UAV shall have imagery intelligence capabilities to support imagery mapping and seeking capabilities.

## #43: UAV Capability (Container)
The system shall provide UAV capability that will support search and rescue missions

### #44: UAV Autonomous Launch and Recover (Functional)
The system shall provide UAV to have autonomous shipboard launch and recover with little or no human interfacing.

#### #45: UAV Launch and Landing Areas (Functional)
The system shall able to launch and land off of a Coast Guard 35-foot long range interceptor II cutter boat.

#### #46: UAV Launch and Recover in High Sea States (Functional)
The system shall to be able to Launch and Recover in sea states five without causing damage to the UAV, ship or crew.

### #47: UAV Autonomous Flying (Functional)
The system shall be able to follow a flight path even if it loses connection with ship’s ground control station.

### #48: UAV Hover Capabilities (Functional)
The system shall maintain position, hover over an area of interest.

### #49: UAV Operation Period (Functional)
The system shall conduct a maximum of 30 minutes of operations for search and rescue missions without recharging.

### #50: UAV Fly Patterns (Functional)
The system shall fly a predetermined pattern in order to conduct search and rescue reconnaissance with either IR sensors or full motion video.

## #51: Justifications

### #52: Verified by inspection
