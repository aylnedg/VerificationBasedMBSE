# SystemRequirements

## #1: Communications Capability (Functional)
The system shall provide communication capabilities to coordinate with launch platform to support search and rescue efforts during missions

## #2: Imaging Capability (Container)
The system shall perform various imaging capabilities for search and rescue

### #3: Image Capture (Functional)
The UAV shall include a payload sensor capable of capturing images in the visible light spectrum.

### #4: Image Processing (Functional)
The UAV shall have image-processing capabilities to support identifying locations of interest and distinguishing lost personnel for search and rescue mission.

### #5: Imagery Intelligence (Functional)
The UAV shall have imagery intelligence capabilities to support imagery mapping and seeking capabilities.

## #6: UAV Capability (Container)
The system shall provide UAV capability that will support search and rescue missions

### #7: UAV Autonomous Flying (Functional)
The system shall be able to follow a flight path even if it loses connection with Ground Control Station

### #8: UAV Hover Capabilities (Functional)
The system shall maintain position, hover over an area of interest

### #9: UAV Operation Period (Functional)
The system shall conduct a maximum of 30 minutes of operations for search and rescue missions without recharging.

### #10: UAV Fly Patterns (Functional)
The system shall fly a predetermined pattern in order to conduct search and rescue reconnaissance with either IR sensors or full motion video

## #11: Aircraft Performance (Container)

### #12: Cruise Speed (Functional)
The UAV cruise speed shall be at least 30 knots

### #13: Max Speed (Functional)
The UAV shall have a max speed of 45 knots

### #14: UAV Operation Period (Functional)
The UAV shall have minimum endurance of 15 minutes loiter at 0.5 m radius

### #15: Operational Radius (Functional)
The UAV shall have an operational radius of 0.5 m while sustaining cruise speed and hovering 5 minutes at the turn around point.

### #16: Recovery Condition (Functional)
The UAV shall be able to be recovered with at least 30% remaining battery capacity.

### #17: Operational Altitude (Functional)
The UAV shall be able to fly at an altitude of at least 500 ft. while maintaining minimum maneuverability requirements.

## #18: Power System (Container)

### #19: Power Source (Functional)
The aircraft battery shall power all aircraft and payload components.

### #20: Sizing (Functional)
The battery shall support a minimum of 15 minutes of flight during normal UAV operation.

## #21: Mass Properties & Geometry (Container)

### #22: Total volume (Functional)
The aircraft with attached payload shall fit inside a 56cm x 36cm x 23cm container.

### #23: Total Mass (Functional)
The aircraft and payload total mass shall be <= 5 kg.

## #24: Flight Control System (Container)

### #25: FCS communications (Container)
The FCS shall send data to and receive data from the Ground Control Station to support safe UAV operation.

#### #26: FCS receive commands (Functional)
The FCS shall recieve commands from the Ground Control Station.

#### #27: FCS send telemetry (Functional)
The FCS shall send telemetry data to the Ground Control Station.

### #28: FCS Modes (Functional)
The FCS shall allow the aircraft to autonomously takeoff, land, and track waypoints or an identified target with necessary safety modes for off-nominal situations.

### #29: FCS Target Tracking (Functional)
The FCS shall receive target position data from the launch platform, combine this with onboard sensor data, and calculate an estimated position of the target relative to the quadcopter.

### #30: FCS Control (Functional)
The FCS shall enable autonomous stable flight with sufficient maneuverability to track waypoints or an identified target.
