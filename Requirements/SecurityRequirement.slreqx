# SecurityRequirement

## #2: GCS to UAV Communication Security (Functional)
The communication channel between the Ground Control Station (GCS) and the UAV shall use a custom protocol that is not publicly documented.
