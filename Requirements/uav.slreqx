# uav

## #1: Aircraft Performance (Container)

### #2: Cruise Speed (Functional)
The UAV cruise speed shall be at least 30 knots.

### #3: Max Speed (Functional)
The UAV shall have a max speed of 45 knots.

### #4: UAV Operation Period (Functional)
The UAV shall have minimum endurance of 15 minutes loiter at 0.5 m radius.

### #5: Operational Radius (Functional)
The UAV shall have an operational radius of 0.5 m while sustaining cruise speed and hovering 5 minutes at the turn around point.

### #6: Recovery Condition (Functional)
The UAV shall be able to be recovered with at least 30% remaining battery capacity.

### #7: Operational Altitude (Functional)
The UAV shall be able to fly at an altitude of at least 500 ft. while maintaining minimum maneuverability requirements.

## #8: Power System (Container)

### #9: Power Source (Functional)
The aircraft battery shall power all aircraft and payload components.

### #10: Sizing (Functional)
The battery shall support a minimum of 15 minutes of flight during normal UAV operation.

## #11: Mass Properties & Geometry (Container)

### #12: Total volume (Functional)
The aircraft with attached payload shall fit inside a 56cm x 36cm x 23cm container.

### #13: Total Mass (Functional)
The aircraft and payload total mass shall be <= 5 kg.

## #14: Flight Control System (Container)

### #15: FCS communications (Container)
The FCS shall send data to and receive data from the Ground Control Station to support safe UAV operation.

#### #25: FCS receive commands (Functional)
The FCS shall recieve commands from the Ground Control Station.

#### #26: FCS send telemetry (Functional)
The FCS shall send telemetry data to the Ground Control Station.

### #16: FCS Modes (Functional)
The FCS shall allow the aircraft to autonomously takeoff, land, and track waypoints or an identified target with necessary safety modes for off-nominal situations.

### #17: FCS Target Tracking (Functional)
The FCS shall receive target position data from the launch platform, combine this with onboard sensor data, and calculate an estimated position of the target relative to the quadcopter.

### #18: FCS Control (Functional)
The FCS shall enable autonomous stable flight with sufficient maneuverability to track waypoints or an identified target.

## #19: Payload (Container)

### #20: Power source (Functional)
The payload shall draw power from the aircraft battery

#### #21: Power switch (Functional)
The payload sensor shall be able to be powered on/off independently from the aircraft

### #22: Payload sensor (Functional)
The payload sensor shall be a visible light spectrum camera

### #23: Max Payload Weight (Functional)
The mission payload shall be not less than 200 lbs total in four individually deployable segments 50 lb or more.
- Rationale: Suspected copy-paste error — inconsistent with uav #13 (total mass <= 5 kg). Requires authoring correction.
- Keywords: REVIEW

## #24: Image Processing (Functional)
UAV can detect down personnel
