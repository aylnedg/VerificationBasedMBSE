# variant_comms

## REQ-VAR-001: MAVLink Protocol Compliance (Functional)
When varComms==1, FCS shall use MAVLink message format for all GCS communications.
- Rationale: Ensures interoperability with standard GCS software in MAVLink variant.

## REQ-VAR-002: Custom Protocol Isolation (Functional)
When varComms==0, FCS shall use proprietary encrypted protocol. MAVLink blocks shall not be active.
- Rationale: Prevents protocol leakage between variants in generated code.

## REQ-VAR-003: Threat Detection Capability (Functional)
When varThreat==1, system shall detect and log spoofed command injection attempts.
- Rationale: Security posture active only in adversarial mission configuration.
