# gcs

## #1: Operator Interface (Container)

### #2: Operator Commands (Functional)
The GCS shall provide capability for an operator to send commands to the vehicle.

### #3: Operator Situational Awareness (Functional)
The operator shall receive sufficient telemetry data from the vehicle to correctly determine the safety, security, and effectiveness of the system.
